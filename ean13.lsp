;Author skvamme
;Draw EAN13 type Barcode
(defun C:EAN13 (/ tab xy n e pos land tp pt )

(setq tab
'((0 ((12 A)(11 A)(10 A)(9 A)(8 A)(7 A)))
  (1 ((12 A)(11 A)(10 B)(9 A)(8 B)(7 B)))
  (2 ((12 A)(11 A)(10 B)(9 B)(8 A)(7 B)))
  (3 ((12 A)(11 A)(10 B)(9 B)(8 B)(7 A)))
  (4 ((12 A)(11 B)(10 A)(9 A)(8 B)(7 B)))
  (5 ((12 A)(11 B)(10 B)(9 A)(8 A)(7 B)))
  (6 ((12 A)(11 B)(10 B)(9 B)(8 A)(7 A)))
  (7 ((12 A)(11 B)(10 A)(9 B)(8 A)(7 B)))
  (8 ((12 A)(11 B)(10 A)(9 B)(8 B)(7 A)))
  (9 ((12 A)(11 B)(10 B)(9 A)(8 B)(7 A)))
))

(setq xy
'((A ((0 (0.33 0.66 1.32 22.85))(1 (0.30 0.99 1.62 22.85))
  (2 (0.63 1.32 1.62 22.85))(3 (0.33 0.66 1.98 22.85))
  (4 (0.66 1.65 1.98 22.85))(5 (0.33 1.32 1.98 22.85))
  (6 (1.32 1.65 1.98 22.85))(7 (0.69 0.99 2.01 22.85))
  (8 (1.02 1.32 2.01 22.85))(9 (0.66 0.99 1.32 22.85))
  (10(0.33 0.66 0.99 24.50))))
  (B ((0 (0.99 1.65 1.98 22.85))(1 (0.69 1.32 2.01 22.85))
  (2 (0.69 0.99 1.68 22.85))(3 (0.33 1.65 1.98 22.85))
  (4 (0.33 0.66 1.65 22.85))(5 (0.33 0.99 1.98 22.85))
  (6 (0.33 0.66 0.99 22.85))(7 (0.30 1.32 1.62 22.85))
  (8 (0.30 0.99 1.29 22.85))(9 (0.99 1.32 1.65 22.85))
  (10(0.33 0.66 0.99 24.50))))
))

(defun a_or_b (land pos /)
  (if (=(cadr(assoc pos (cadr(assoc land tab))))'A) 'A 'B)
)

(defun draw(A p x / A p x nv1 nh1 ”v1 ”h2 nv2 nh2 ”v2 ”h2 l)
  (if (or(= A 'A)(= A 'B))(progn
    (setq l(cadr(assoc x(cadr(assoc A xy)))))
    (setq nh2 p)
    (setq nv1 (list(-(car nh2)(caddr l))(cadr nh2)))
    (setq nh1 (list(-(car nh2)(cadr l))(cadr nh2)))
    (setq ”v1 (list(car nv1)(+(cadr nh2)(cadddr l))))
    (setq ”h1 (list(car nh1)(cadr ”v1)))
    (setq nv2 (list(-(car nh2)(car l))(cadr nh2)))
    (setq ”v2 (list(car nv2)(cadr ”v1)))
    (setq ”h2 (list(car nh2)(cadr ”v1)))
    (command "SOLID" nv1 nh1 ”v1 ”h1 "")
    (command "SOLID" nv2 nh2 ”v2 ”h2 "")
  ))
  (if (= A 'C)(progn
    (setq l(cadr(assoc x(cadr(assoc 'B xy)))))
    (setq nv1 p)
    (setq nh1 (list(+(car nv1)(car l))(cadr nv1)))
    (setq ”v1 (list(car nv1)(+(cadr nv1)(cadddr l))))
    (setq ”h1 (list(car nh1)(cadr ”v1)))
    (setq nv2 (list(+(car nv1)(cadr l))(cadr nv1)))
    (setq nh2 (list(+(car nv1)(caddr l))(cadr nv1)))
    (setq ”v2 (list(car nv2)(cadr ”v1)))
    (setq ”h2 (list(car nh2)(cadr ”v1)))
    (command "SOLID" nv1 nh1 ”v1 ”h1 "")
    (command "SOLID" nv2 nh2 ”v2 ”h2 "")
  ))
)

(defun cutmark (/ lr ul ur)
  (setq lr (list(+(car ll)37.29)(cadr ll)))
  (setq ul (list(car ll)(+(cadr ll)26.26)))
  (setq ur (list(car lr)(cadr ul)))
  (command "LINE" ll "@5<180" "" "LINE" ll "@5<-90" "")
  (command "LINE" lr "@5<0" "" "LINE" lr "@5<-90" "")
  (command "LINE" ul "@5<180" "" "LINE" ul "@5<90" "")
  (command "LINE" ur "@5<0" "" "LINE" ur "@5<90" "")
)

(defun readnr (/ eannr nr n knr knrstr jpos upos)
  (setq eannr(getstring "\nType Barcode: (13 digits) "))
  (if (/=(strlen eannr)13)(readnr))
  (setq e '() n 1)
  (repeat 13
    (setq nr(atoi(substr eannr n 1)))
    (setq e (cons nr e))
    (setq n (1+ n))
  )
  (setq jpos(+(nth 1 e)(nth 3 e)(nth 5 e)
              (nth 7 e)(nth 9 e)(nth 11 e)))
  (setq upos(+(nth 2 e)(nth 4 e)(nth 6 e)
              (nth 8 e)(nth 10 e)(nth 12 e)))
  (setq knrstr (itoa(+(* 3 jpos)upos)))
  (setq knr(- 10(atoi(substr knrstr(strlen knrstr)1))))
  (if (= knr 10)(setq knr 0))
  (if (/= knr (car e))(progn
    (princ "*Checksum ERROR*, Correcting to ")
    (princ knr)
    (setq e (cons knr(cdr e)))
  ))
  (setq e(reverse e))
)

(command "SETVAR" "TEXTEVAL" "1")
(readnr)
(setq ll (getpoint "\nBase point: "))
(cutmark)
(setq land (car e) pos 13 tp ll)
(command "TEXT" tp "2.75" "0" (car e))
(setq tp (list(+(car tp)4.92)(cadr tp)))
(setq pt(list(+(car ll) 4.62)(+(cadr ll)1.43)))
(draw 'A pt 10);
(setq pt(list(car pt)(+(cadr pt)1.65)))
(setq e (cdr e))

(repeat 6
  (command "TEXT" tp "2.75" "0" (car e))
  (setq tp (list(+(car tp)2.31)(cadr tp)))
  (setq pos (1- pos))
  (setq pt (list(+(car pt) 2.31)(cadr pt)))
  (draw (a_or_b land pos) pt (car e))
  (setq e (cdr e))
)

(setq pt (list(+(car pt) 1.32)(-(cadr pt)1.65)))
(draw 'A pt 10);
(setq pt (list(+(car pt) 0.33)(+(cadr pt)1.65)))
(setq tp (list(+(car tp)1.32)(cadr tp)))

(repeat 6
  (command "TEXT" tp "2.75" "0" (car e))
  (setq tp (list(+(car tp)2.31)(cadr tp)))
  (draw 'C pt (car e))
  (setq pt (list(+(car pt) 2.31)(cadr pt)))
  (setq e (cdr e))
)

(setq pt(list(car pt)(-(cadr pt)1.65)))
(draw 'C pt 10);
(command "SETVAR" "TEXTEVAL" "0")
)
